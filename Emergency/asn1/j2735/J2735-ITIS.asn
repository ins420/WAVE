ITIS
{joint-iso-itu-t (2) country (16) us (840) organization (1) sae (114566)
v2x-communications (1) technical-committees (1) v2x-core (5) technical-reports (1)
j2735 (2735) part-0 (0) asn1-module (1) itis (6) version-1 (1)}
DEFINITIONS AUTOMATIC TAGS ::=
BEGIN

 
 
GenericLocations ::= ENUMERATED  { 
   -- Road Related
   on-bridges                  (7937),  -- Not to be used as the default for this
                                        -- category
   in-tunnels                  (7938),  
   entering-or-leaving-tunnels (7939),  
   on-ramps                    (7940),  
   in-road-construction-area   (7941),  
   around-a-curve              (7942),  
   on-curve                    (8026),   
   on-tracks                   (8009),   
   in-street                   (8025),  -- As in in-street pad crossing
   shoulder                    (8027),   
   on-minor-roads              (7943),  
   in-the-opposing-lanes       (7944),  
   adjacent-to-roadway         (7945),  
   across-tracks               (8024),   
   on-bend                     (7946),  
   intersection                (8032),   
   entire-intersection         (7947),  
   in-the-median               (7948),  
   moved-to-side-of-road       (7949),  
   moved-to-shoulder           (7950),  
   on-the-roadway              (7951),  -- Use generic locations/groups affected to
                                        -- make other such phrases
   dip                         (8010),   
   traffic-circle              (8011),  -- Used for W2-6 graphic as well. Alt term:
                                        -- roundabout
   crossover                   (8028),  
   cross-road                  (8029),  -- Also used for W2-1 Note that in some uses
                                        -- this is one word
   side-road                   (8030),  -- Do not used for W2-2R and W2-2L
   to                          (8014),   
   by                          (8015),   
   through                     (8016),   
   area-of                     (8017),  -- Also area
   under                       (8018),     
   over                        (8019),   
   from                        (8020),   
   approaching                 (8021),   
   entering-at                 (8022),  -- Alt form: Entrance
   exiting-at                  (8023),  
   -- Terrain & Geography
   in-shaded-areas             (7952),  
   in-low-lying-areas          (7953),  
   in-the-downtown-area        (7954),  
   in-the-inner-city-area      (7955),  
   in-parts                    (7956),  
   in-some-places              (7957),  
   in-the-ditch                (7958),  
   in-the-valley               (7959),  
   on-hill-top                 (7960),  
   near-the-foothills          (7961),  
   at-high-altitudes           (7962),  
   near-the-lake               (7963),  
   near-the-shore              (7964),  
   nearby-basin                (8008),  
   over-the-crest-of-a-hill    (7965),  
   other-than-on-the-roadway   (7966),  
   near-the-beach              (7967),  
   near-beach-access-point     (7968),  
   mountain-pass               (8006),  
   lower-level                 (7969),  
   upper-level                 (7970),  
   -- Transit Travel, Air Travel and Places
   airport                     (7971),  
   concourse                   (7972),  
   gate                        (7973),  
   baggage-claim               (7974),  
   customs-point               (7975),  
   reservation-center          (8007),  
   station                     (7976),  
   platform                    (7977),  -- Alternative Rendering:  track
   dock                        (7978),  
   depot                       (7979),  
   ev-charging-point           (7980),  
   information-welcome-point   (7981),  -- Use for Tourist Information as well (D9-10)
   at-rest-area                (7982),  
   at-service-area             (7983),  
   at-weigh-station            (7984),  
   roadside-park               (8033),  
   picnic-areas                (7985),  
   rest-area                   (7986),  
   service-stations            (7987),  
   toilets                     (7988),  -- Note also rest rooms in structures
   bus-stop                    (8031),  
   park-and-ride-lot           (8012),  -- Not to be used as a mode of travel
   -- Direction of Travel
   on-the-right                (7989),  
   on-the-left                 (7990),  
   in-the-center               (7991),  
   in-the-opposite-direction   (7992),  
   cross-traffic               (7993),  
   northbound-traffic          (7994),  
   eastbound-traffic           (7995),  
   southbound-traffic          (7996),  
   westbound-traffic           (7997),  
   -- Compass Points
   north                       (7998),  
   south                       (7999),  
   east                        (8000),  
   west                        (8001),  
   northeast                   (8002),  
   northwest                   (8003),  
   southeast                   (8004),  
   southwest                   (8005),  
   ... -- # LOCAL_CONTENT_ITIS 
   }


IncidentResponseEquipment ::= ENUMERATED { 
   ground-fire-suppression          (9985),   
   heavy-ground-equipment           (9986),   
   aircraft                         (9988),   
   marine-equipment                 (9989),   
   support-equipment                (9990),   
   medical-rescue-unit              (9991),   
   other                            (9993),   -- Depreciated by fire standards, do not
                                              -- use
   ground-fire-suppression-other    (9994),   
   engine                           (9995),   
   truck-or-aerial                  (9996),   
   quint                            (9997),   -- A five-function type of fire 
                                              -- apparatus. The units in the 
                                              -- movie Backdraft were quints
   tanker-pumper-combination        (9998),   
   brush-truck                      (10000),  
   aircraft-rescue-firefighting     (10001),  
   heavy-ground-equipment-other     (10004),  
   dozer-or-plow                    (10005),  
   tractor                          (10006),  
   tanker-or-tender                 (10008),  
   aircraft-other                   (10024),  
   aircraft-fixed-wing-tanker       (10025),  
   helitanker                       (10026),  
   helicopter                       (10027),  
   marine-equipment-other           (10034),  
   fire-boat-with-pump              (10035),  
   boat-no-pump                     (10036),  
   support-apparatus-other          (10044),  
   breathing-apparatus-support      (10045),  
   light-and-air-unit               (10046),  
   medical-rescue-unit-other        (10054),  
   rescue-unit                      (10055),  
   urban-search-rescue-unit         (10056),  
   high-angle-rescue                (10057),  
   crash-fire-rescue                (10058),  
   bLS-unit                         (10059),  
   aLS-unit                         (10060),  
   mobile-command-post              (10075),  -- Depreciated, do not use
   chief-officer-car                (10076),  
   hAZMAT-unit                      (10077),  
   type-i-hand-crew                 (10078),  
   type-ii-hand-crew                (10079),  
   privately-owned-vehicle          (10083),  -- (Often found in volunteer fire teams)
   other-apparatus-resource         (10084),  -- (Remapped from fire code zero)
   ambulance                        (10085),  
   bomb-squad-van                   (10086),  
   combine-harvester                (10087),  
   construction-vehicle             (10088),  
   farm-tractor                     (10089),  
   grass-cutting-machines           (10090),  
   hAZMAT-containment-tow           (10091),  
   heavy-tow                        (10092),  
   light-tow                        (10094),  
   flatbed-tow                      (10114), 
   hedge-cutting-machines           (10093),  
   mobile-crane                     (10095),  
   refuse-collection-vehicle        (10096),  
   resurfacing-vehicle              (10097),  
   road-sweeper                     (10098),  
   roadside-litter-collection-crews (10099),  
   salvage-vehicle                  (10100),  
   sand-truck                       (10101),  
   snowplow                         (10102),  
   steam-roller                     (10103),  
   swat-team-van                    (10104),  
   track-laying-vehicle             (10105),  
   unknown-vehicle                  (10106),  
   white-lining-vehicle             (10107),  -- Consider using Roadwork "road marking
                                              -- operations" unless objective is to
                                              -- refer to the specific vehicle of this
                                              -- type.  Alternative Rendering: line
                                              -- painting vehicle
   dump-truck                       (10108),  
   supervisor-vehicle               (10109),  
   snow-blower                      (10110),  
   rotary-snow-blower               (10111),  
   road-grader                      (10112),  -- Alternative term: motor grader
   steam-truck                      (10113),  -- A special truck that thaws culverts 
                                              -- and storm drains
   ... -- # LOCAL_CONTENT_ITIS 
   }

ITIStext ::= IA5String (SIZE(1..500))

ResponderGroupAffected ::= ENUMERATED { 
   emergency-vehicle-units           (9729),  -- Default, to be used when one of
                                              -- the below does not fit better
   federal-law-enforcement-units     (9730),  
   state-police-units                (9731),  
   county-police-units               (9732),  -- Hint: also sheriff response units
   local-police-units                (9733),  
   ambulance-units                   (9734),  
   rescue-units                      (9735),  
   fire-units                        (9736),  
   hAZMAT-units                      (9737),  
   light-tow-unit                    (9738),  
   heavy-tow-unit                    (9739),  
   freeway-service-patrols           (9740),  
   transportation-response-units     (9741),  
   private-contractor-response-units (9742),  
   ... -- # LOCAL_CONTENT_ITIS 
   }
   -- These groups are used in coordinated response and staging area information
   -- (rather than typically consumer related)

VehicleGroupAffected ::= ENUMERATED { 
   all-vehicles                               (9217),  
   bicycles                                   (9218),  
   motorcycles                                (9219),  -- to include mopeds as well
   cars                                       (9220),  -- (remapped from ERM value of
                                                       -- zero)
   light-vehicles                             (9221),  
   cars-and-light-vehicles                    (9222),  
   cars-with-trailers                         (9223),  
   cars-with-recreational-trailers            (9224),  
   vehicles-with-trailers                     (9225),  
   heavy-vehicles                             (9226),  
   trucks                                     (9227),  
   buses                                      (9228),  
   articulated-buses                          (9229),  
   school-buses                               (9230),  
   vehicles-with-semi-trailers                (9231),  
   vehicles-with-double-trailers              (9232),  -- Alternative Rendering:  
                                                       -- western doubles
   high-profile-vehicles                      (9233),  
   wide-vehicles                              (9234),  
   long-vehicles                              (9235),  
   hazardous-loads                            (9236),  
   exceptional-loads                          (9237),  
   abnormal-loads                             (9238),  
   convoys                                    (9239),  
   maintenance-vehicles                       (9240),  
   delivery-vehicles                          (9241),  
   vehicles-with-even-numbered-license-plates (9242),  
   vehicles-with-odd-numbered-license-plates  (9243),  
   vehicles-with-parking-permits              (9244),  
   vehicles-with-catalytic-converters         (9245),  
   vehicles-without-catalytic-converters      (9246),  
   gas-powered-vehicles                       (9247),  
   diesel-powered-vehicles                    (9248),  
   lPG-vehicles                               (9249),  -- The L is lower case here
   military-convoys                           (9250),  
   military-vehicles                          (9251),  
   ... -- # LOCAL_CONTENT_ITIS 
   }
   -- Classification of vehicles and types of transport

ITIScodesAndText ::= SEQUENCE (SIZE(1..100)) OF SEQUENCE {
  item CHOICE    {
       itis ITIScodes,
       text ITIStext
       } -- # UNTAGGED
  }

ITIScodes ::= INTEGER (0..65535)
END
